;;; Dino 8 reference-output harness for AutoCAD (AutoLISP + Visual LISP ActiveX).
;;; STATUS: UNTESTED against a real AutoCAD installation. Written from the public AutoCAD
;;; ActiveX / AutoLISP documentation. Every scenario runs under vl-catch-all-apply, so a failure
;;; is recorded and the run continues.
;;;
;;; SAFETY
;;;  - Refuses to run unless the active drawing is EMPTY. Open a new drawing first (command QNEW).
;;;  - Creates test geometry, measures it, then erases all of it. Never saves, never uses SAVEAS.
;;;  - Writes only inside the output folder (d8:path rejects names with slashes or "..").
;;;  - No network calls. FILEDIA, CMDECHO and EXPERT are changed temporarily and restored at the end.
;;; RUN
;;;  1. QNEW (empty drawing).  2. APPLOAD this file (or: (load "C:/path/d8_reference_autocad.lsp")).
;;;  3. Command:  D8REF   -> asks for the output folder (or set the environment variable D8_REF_OUT).
;;; EULA: counsel must confirm that scripted observation is permitted before this is run.

(vl-load-com)
(setq *d8-version* "0.1.0")

;;; ---------------------------------------------------------------- JSON writer
;;; (cons 'OBJ alist) = object, (cons 'ARR list) = array, T = true, nil = null.
(defun d8:esc (s / out i c)
  (setq out "" i 1)
  (while (<= i (strlen s))
    (setq c (substr s i 1))
    (cond ((= c "\"") (setq out (strcat out "\\\"")))
          ((= c "\\") (setq out (strcat out "\\\\")))
          ((= c "\n") (setq out (strcat out "\\n")))
          ((< (ascii c) 32) (setq out (strcat out " ")))
          (T (setq out (strcat out c))))
    (setq i (1+ i)))
  out)
(defun d8:js (x / out first kv)
  (cond
    ((null x) "null")
    ((eq x T) "true")
    ((numberp x) (rtos x 2 9))
    ((= (type x) 'STR) (strcat "\"" (d8:esc x) "\""))
    ((= (type x) 'SYM) (strcat "\"" (vl-symbol-name x) "\""))
    ((and (listp x) (eq (car x) 'OBJ))
     (setq out "{" first T)
     (foreach kv (cdr x)
       (setq out (strcat out (if first "" ",") "\"" (d8:esc (car kv)) "\":" (d8:js (cdr kv))) first nil))
     (strcat out "}"))
    ((and (listp x) (eq (car x) 'ARR))
     (setq out "[" first T)
     (foreach kv (cdr x) (setq out (strcat out (if first "" ",") (d8:js kv)) first nil))
     (strcat out "]"))
    (T (strcat "\"" (d8:esc (vl-prin1-to-string x)) "\""))))
(defun d8:obj (al) (cons 'OBJ al))
(defun d8:arr (l) (cons 'ARR l))

;;; ---------------------------------------------------------------- output folder
(defun d8:mkdirs (p / parts acc)
  (setq p (vl-string-translate "\\" "/" p) acc "")
  (foreach part (d8:split p "/")
    (setq acc (if (= acc "") part (strcat acc "/" part)))
    (if (and (> (strlen part) 0) (not (vl-file-directory-p acc)) (not (= (substr part (strlen part)) ":")))
      (vl-mkdir acc)))
  (vl-file-directory-p p))
(defun d8:split (s d / out pos)
  (setq out nil)
  (while (setq pos (vl-string-search d s))
    (setq out (cons (substr s 1 pos) out) s (substr s (+ pos 1 (strlen d)))))
  (reverse (cons s out)))
(defun d8:path (name)
  (if (or (vl-string-search "/" name) (vl-string-search "\\" name) (vl-string-search ".." name))
    (progn (princ (strcat "\nREFUSED unsafe file name: " name)) (exit)))
  (strcat *d8-out* "/" name))
(defun d8:write (name text / f)
  (setq f (open (d8:path name) "w"))
  (write-line text f)
  (close f))

;;; ---------------------------------------------------------------- geometry helpers
(defun d8:pt (x y z) (vlax-3d-point x y z))
(defun d8:dbls (l) (vlax-make-variant (vlax-safearray-fill (vlax-make-safearray vlax-vbdouble (cons 0 (1- (length l)))) l)))
(defun d8:lwpoly (pts closed / o)
  (setq o (vla-AddLightWeightPolyline *d8-ms* (d8:dbls (apply 'append pts))))
  (if closed (vla-put-Closed o :vlax-true))
  o)
(defun d8:rect (w h) (list (list 0.0 0.0) (list w 0.0) (list w h) (list 0.0 h)))
(defun d8:region (curve / arr res)
  (setq arr (vlax-make-safearray vlax-vbObject '(0 . 0)))
  (vlax-safearray-put-element arr 0 curve)
  (setq res (vla-AddRegion *d8-ms* (vlax-make-variant arr)))
  (car (vlax-safearray->list (vlax-variant-value res))))
(defun d8:bbox (o / mn mx)
  (vla-GetBoundingBox o 'mn 'mx)
  (d8:obj (list (cons "min" (d8:arr (vlax-safearray->list (vlax-variant-value mn))))
                (cons "max" (d8:arr (vlax-safearray->list (vlax-variant-value mx)))))))
(defun d8:solid-info (o)
  (d8:obj (list (cons "type" (vla-get-ObjectName o))
                (cons "volume" (vl-catch-all-apply-val '(lambda () (vla-get-Volume o))))
                (cons "centroid" (vl-catch-all-apply-val '(lambda () (d8:arr (vlax-safearray->list (vlax-variant-value (vla-get-Centroid o)))))))
                (cons "principal_moments" (vl-catch-all-apply-val '(lambda () (d8:arr (vlax-safearray->list (vlax-variant-value (vla-get-PrincipalMoments o)))))))
                (cons "bbox" (vl-catch-all-apply-val '(lambda () (d8:bbox o)))))))
(defun vl-catch-all-apply-val (fn / r)
  (setq r (vl-catch-all-apply fn nil))
  (if (vl-catch-all-error-p r) (strcat "ERROR: " (vl-catch-all-error-message r)) r))

;;; ---------------------------------------------------------------- scenarios
(defun d8:s01 (/ o) (setq o (vla-AddBox *d8-ms* (d8:pt 50.0 30.0 0.0) 100.0 60.0 40.0))
  (list (cons "expected_volume" 240000.0) (cons "solid" (d8:solid-info o))))
(defun d8:s02 (/ o) (setq o (vla-AddCylinder *d8-ms* (d8:pt 0.0 0.0 0.0) 15.0 40.0))
  (list (cons "expected_volume" (* pi 225.0 40.0)) (cons "solid" (d8:solid-info o))))
(defun d8:s03 (/ o) (setq o (vla-AddSphere *d8-ms* (d8:pt 0.0 0.0 0.0) 25.0))
  (list (cons "expected_volume" (* (/ 4.0 3.0) pi 25.0 25.0 25.0)) (cons "solid" (d8:solid-info o))))
(defun d8:s04 (/ c r o)
  (setq c (vla-AddCircle *d8-ms* (d8:pt 0.0 0.0 0.0) 20.0) r (d8:region c)
        o (vla-AddExtrudedSolid *d8-ms* r 50.0 (atan (/ 10.0 50.0))))
  (list (cons "note" "frustum by tapered extrusion; taper angle in radians")
        (cons "expected_volume" (* pi (/ 50.0 3.0) (+ 400.0 200.0 100.0))) (cons "solid" (d8:solid-info o))))
(defun d8:edge-cmd (cmd opt / o before)
  (setq o (vla-AddBox *d8-ms* (d8:pt 50.0 30.0 0.0) 100.0 60.0 40.0))
  (command "_.ZOOM" "_E") (command "_.-VIEW" "_SWISO")
  (command cmd opt 5.0 (list 0.0 0.0 20.0) "" "")
  (while (> (getvar "CMDACTIVE") 0) (command ""))
  (list (cons "note" "edge picked by point at the corner edge (0,0,20); depends on the view; result may be unchanged if the pick missed")
        (cons "solid" (d8:solid-info o))))
(defun d8:s05 () (d8:edge-cmd "_.CHAMFEREDGE" "_D"))
(defun d8:s06 () (d8:edge-cmd "_.FILLETEDGE" "_R"))
(defun d8:bool (op / a b)
  (setq a (vla-AddBox *d8-ms* (d8:pt 50.0 30.0 0.0) 100.0 60.0 40.0)
        b (vla-AddCylinder *d8-ms* (d8:pt 50.0 30.0 -5.0) 10.0 50.0))
  (vla-Boolean a op b)
  a)
(defun d8:s07 (/ a) (setq a (d8:bool 2)) (list (cons "expected_volume" (- 240000.0 (* pi 100.0 40.0))) (cons "solid" (d8:solid-info a))))
(defun d8:s08 (/ a) (setq a (d8:bool 0)) (list (cons "solid" (d8:solid-info a))))
(defun d8:s09 (/ a) (setq a (d8:bool 1)) (list (cons "expected_volume" (* pi 100.0 40.0)) (cons "solid" (d8:solid-info a))))
(defun d8:s10 (/ p out r)
  (setq p (d8:lwpoly (d8:rect 100.0 60.0) T) out nil)
  (foreach d '(5.0 -5.0)
    (setq r (vl-catch-all-apply 'vla-Offset (list p d)))
    (setq out (cons (cons (if (> d 0) "offset_+5" "offset_-5")
                          (if (vl-catch-all-error-p r) (vl-catch-all-error-message r)
                              (d8:obj (list (cons "length" (vla-get-Length (car (vlax-safearray->list (vlax-variant-value r)))))
                                            (cons "area" (vla-get-Area (car (vlax-safearray->list (vlax-variant-value r)))))))))
                    out)))
  (append (list (cons "original_length" (vla-get-Length p)) (cons "original_area" (vla-get-Area p))
                (cons "expected_sharp_outer_length" 360.0) (cons "expected_sharp_inner_length" 280.0)) (reverse out)))
(defun d8:s11 (/ c) (setq c (vla-AddCircle *d8-ms* (d8:pt 0.0 0.0 0.0) 20.0))
  (list (cons "circumference" (vla-get-Circumference c)) (cons "area" (vla-get-Area c)) (cons "expected_circumference" (* 2.0 pi 20.0)) (cons "expected_area" (* pi 400.0))))
(defun d8:s12 (/ p r o) (setq p (d8:lwpoly (d8:rect 50.0 30.0) T) r (d8:region p) o (vla-AddExtrudedSolid *d8-ms* r 20.0 0.0))
  (list (cons "expected_volume" 30000.0) (cons "solid" (d8:solid-info o))))
(defun d8:s13 (/ p r o)
  (setq p (d8:lwpoly (list (list 10.0 0.0) (list 30.0 0.0) (list 30.0 20.0) (list 10.0 20.0)) T) r (d8:region p)
        o (vla-AddRevolvedSolid *d8-ms* r (d8:pt 0.0 0.0 0.0) (d8:pt 0.0 1.0 0.0) (* 2.0 pi)))
  (list (cons "note" "profile drawn in the XY plane and revolved about the Y axis") (cons "expected_volume" (* pi 800.0 20.0)) (cons "solid" (d8:solid-info o))))
(defun d8:s14 (/ o)
  (setq o (vla-AddBox *d8-ms* (d8:pt 50.0 30.0 0.0) 100.0 60.0 40.0))
  (vla-Rotate o (d8:pt 0.0 0.0 0.0) (/ pi 4.0))
  (list (cons "rotated_45" (d8:solid-info o)) (cons "expected_volume" 240000.0)))
(defun d8:s15 (/ o r)
  (setq o (vla-AddBox *d8-ms* (d8:pt 5.0 5.0 0.0) 10.0 10.0 10.0))
  (setq r (vl-catch-all-apply 'vla-ArrayRectangular (list o 1 5 1 0.0 20.0 0.0)))
  (list (cons "result" (if (vl-catch-all-error-p r) (vl-catch-all-error-message r) "array created"))
        (cons "object_count_in_model_space" (vla-get-Count *d8-ms*))))
(defun d8:s16 (/ o s)
  (setq o (vla-AddBox *d8-ms* (d8:pt 50.0 30.0 0.0) 100.0 60.0 40.0))
  (setq s (vla-SliceSolid o (d8:pt 0.0 0.0 20.0) (d8:pt 1.0 0.0 20.0) (d8:pt 0.0 1.0 20.0) :vlax-true))
  (list (cons "lower_half" (d8:solid-info o)) (cons "upper_half" (d8:solid-info s)) (cons "expected_each_volume" 120000.0)))
(defun d8:s17 (/ a b i)
  (setq a (vla-AddBox *d8-ms* (d8:pt 50.0 30.0 0.0) 100.0 60.0 40.0) b (vla-AddBox *d8-ms* (d8:pt 100.0 30.0 0.0) 100.0 60.0 40.0))
  (setq i (vla-CheckInterference a b :vlax-true))
  (list (cons "interferes" (if (= (vl-catch-all-apply 'vla-get-Volume (list i)) 0) nil T))
        (cons "interference_solid" (if (vl-catch-all-error-p i) nil (d8:solid-info i))) (cons "expected_overlap_volume" (* 50.0 60.0 40.0))))
(defun d8:s18 (/ d)
  (setq d (vla-AddDimAligned *d8-ms* (d8:pt 0.0 0.0 0.0) (d8:pt 100.0 0.0 0.0) (d8:pt 50.0 10.0 0.0)))
  (list (cons "measurement" (vla-get-Measurement d)) (cons "text" (vla-get-TextOverride d)) (cons "dimstyle" (vla-get-StyleName d))))
(defun d8:s19 (/ c l r)
  (setq c (vla-AddCircle *d8-ms* (d8:pt 0.0 0.0 0.0) 20.0) l (vla-AddLine *d8-ms* (d8:pt -30.0 0.0 0.0) (d8:pt 30.0 0.0 0.0)))
  (setq r (vla-IntersectWith c l 0))
  (list (cons "points" (d8:arr (vlax-safearray->list (vlax-variant-value r)))) (cons "expected" "(-20,0,0) and (20,0,0)")))
(defun d8:try-export (tag cmdlist file / ok p)
  (setq p (d8:path file))
  (setq ok (vl-catch-all-apply '(lambda () (eval (cons 'command cmdlist)))))
  (while (> (getvar "CMDACTIVE") 0) (command ""))
  (cons tag (d8:obj (list (cons "ok" (if (vl-catch-all-error-p ok) nil T))
                          (cons "error" (if (vl-catch-all-error-p ok) (vl-catch-all-error-message ok) nil))
                          (cons "exists" (if (findfile p) T nil))
                          (cons "bytes" (if (findfile p) (vl-file-size p) 0))))))
(defun d8:s20 (/ a b res ss)
  (setq a (vla-AddBox *d8-ms* (d8:pt 50.0 30.0 0.0) 100.0 60.0 40.0) b (vla-AddCylinder *d8-ms* (d8:pt 50.0 30.0 -5.0) 10.0 50.0))
  (vla-Boolean a 2 b)
  (setq ss (ssget "_X"))
  (setq res
    (list (d8:try-export "dxf" (list "_.DXFOUT" (d8:path "scenario20_result.dxf") "16") "scenario20_result.dxf")
          (d8:try-export "sat" (list "_.ACISOUT" ss "" (d8:path "scenario20_result.sat")) "scenario20_result.sat")
          (d8:try-export "stl" (list "_.STLOUT" ss "" "_Y" (d8:path "scenario20_result.stl")) "scenario20_result.stl")
          (d8:try-export "step" (list "_.STEPOUT" ss "" (d8:path "scenario20_result.step")) "scenario20_result.step")
          (d8:try-export "iges" (list "_.IGESOUT" ss "" (d8:path "scenario20_result.igs")) "scenario20_result.igs")
          (d8:try-export "fbx" (list "_.FBXEXPORT" ss "" (d8:path "scenario20_result.fbx")) "scenario20_result.fbx")))
  (append res (list (cons "note" "command names that do not exist in this release are recorded as errors; the owner's upload step adds file hashes"))))

(setq *d8-scenarios*
  '(("s01_box" . d8:s01) ("s02_cylinder" . d8:s02) ("s03_sphere" . d8:s03) ("s04_taper_extrude_frustum" . d8:s04)
    ("s05_chamfer_edge" . d8:s05) ("s06_fillet_edge" . d8:s06) ("s07_boolean_difference" . d8:s07) ("s08_boolean_union" . d8:s08)
    ("s09_boolean_intersection" . d8:s09) ("s10_offset_closed_polyline" . d8:s10) ("s11_circle_properties" . d8:s11)
    ("s12_extrude_region" . d8:s12) ("s13_revolve_region" . d8:s13) ("s14_rotate_solid" . d8:s14) ("s15_rectangular_array" . d8:s15)
    ("s16_slice_solid" . d8:s16) ("s17_check_interference" . d8:s17) ("s18_aligned_dimension" . d8:s18)
    ("s19_curve_intersection" . d8:s19) ("s20_export_formats" . d8:s20)))

;;; ---------------------------------------------------------------- enumeration (commands, menus, system variables)
(defun d8:menu-items (menu depth / out i n it)
  (setq out nil i 0 n (vla-get-Count menu))
  (while (< i n)
    (setq it (vl-catch-all-apply 'vla-Item (list menu i)))
    (if (not (vl-catch-all-error-p it))
      (setq out (cons (d8:obj (list (cons "label" (vl-catch-all-apply-val '(lambda () (vla-get-Caption it))))
                                    (cons "macro" (vl-catch-all-apply-val '(lambda () (vla-get-Macro it))))
                                    (cons "type" (vl-catch-all-apply-val '(lambda () (vla-get-Type it))))
                                    (cons "children" (if (and (< depth 6) (= (vl-catch-all-apply-val '(lambda () (vla-get-Type it))) 2))
                                                       (vl-catch-all-apply-val '(lambda () (d8:arr (d8:menu-items (vla-get-SubMenu it) (1+ depth)))))
                                                       nil))))
                      out)))
    (setq i (1+ i)))
  (reverse out))
(defun d8:menus (/ out mg i j)
  (setq out nil)
  (vlax-for mg (vla-get-MenuGroups *d8-acad*)
    (vlax-for pm (vla-get-Menus mg)
      (setq out (cons (d8:obj (list (cons "group" (vla-get-Name mg)) (cons "menu" (vla-get-Name pm)) (cons "items" (d8:arr (d8:menu-items pm 0))))) out))))
  (reverse out))
(defun d8:toolbars (/ out)
  (setq out nil)
  (vlax-for mg (vla-get-MenuGroups *d8-acad*)
    (vlax-for tb (vla-get-Toolbars mg)
      (setq out (cons (d8:obj (list (cons "group" (vla-get-Name mg)) (cons "toolbar" (vla-get-Name tb))
                                    (cons "buttons" (d8:arr (let (r) (vlax-for b tb (setq r (cons (d8:obj (list (cons "name" (vl-catch-all-apply-val '(lambda () (vla-get-Name b))))
                                                                                                          (cons "macro" (vl-catch-all-apply-val '(lambda () (vla-get-Macro b))))
                                                                                                          (cons "help" (vl-catch-all-apply-val '(lambda () (vla-get-HelpString b)))))) r))) (reverse r)))))) out))))
  (reverse out))
(setq *d8-sysvars*
  '("ACADVER" "ACADLSPASDOC" "ANGBASE" "ANGDIR" "AUNITS" "AUPREC" "BLIPMODE" "CECOLOR" "CELTYPE" "CELWEIGHT" "CHAMFERA" "CHAMFERB" "CHAMFERC" "CHAMFERD" "CHAMMODE"
    "CIRCLERAD" "CMDACTIVE" "CMDECHO" "CMDNAMES" "DELOBJ" "DIMASSOC" "DIMSCALE" "DIMSTYLE" "DISPSILH" "DRAGMODE" "DWGNAME" "EDGEMODE" "ELEVATION" "EXPERT" "EXPLMODE"
    "FACETRES" "FIELDEVAL" "FILEDIA" "FILLETRAD" "FILLMODE" "FRONTZ" "GRIDMODE" "HPNAME" "HPSCALE" "INSBASE" "INSUNITS" "INSUNITSDEFSOURCE" "INSUNITSDEFTARGET" "ISOLINES"
    "LASTANGLE" "LASTPOINT" "LAYOUTREGENCTL" "LENSLENGTH" "LIMCHECK" "LIMMAX" "LIMMIN" "LOCALE" "LOGFILEMODE" "LTSCALE" "LUNITS" "LUPREC" "MAXACTVP" "MEASUREMENT"
    "MENUNAME" "MIRRTEXT" "MODEMACRO" "ORTHOMODE" "OSMODE" "PDMODE" "PDSIZE" "PELLIPSE" "PICKBOX" "PLATFORM" "PLINEGEN" "PLINEWID" "PRODUCT" "PROJECTNAME" "PSLTSCALE"
    "REGENMODE" "RELEASE" "SAVEFILE" "SHADEDGE" "SHADEDIF" "SNAPMODE" "SOLIDCHECK" "SPLFRAME" "SPLINESEGS" "SPLINETYPE" "SURFTAB1" "SURFTAB2" "SURFTYPE" "SURFU" "SURFV"
    "TEXTSIZE" "TEXTSTYLE" "THICKNESS" "TILEMODE" "TOOLTIPS" "TRIMMODE" "UCSNAME" "UNITMODE" "USERI1" "VISRETAIN" "WORLDUCS" "XREFCTL" "3DOSMODE" "BACKGROUNDPLOT"
    "VSCURRENT" "VIEWMODE" "TARGET" "VIEWDIR" "VSMAX" "VSMIN" "NAVVCUBEDISPLAY" "SELECTIONPREVIEW" "MESHTYPE" "SURFACEASSOCIATIVITY" "SOLIDHIST" "SHOWHIST" "DELOBJ"))
(defun d8:sysvars (/ out v)
  (setq out nil)
  (foreach n *d8-sysvars*
    (setq v (vl-catch-all-apply 'getvar (list n)))
    (setq out (cons (cons n (if (vl-catch-all-error-p v) "n/a" (if (listp v) (d8:arr v) v))) out)))
  (d8:obj (reverse out)))
(defun d8:lisp-commands (/ out)
  (setq out nil)
  (foreach a (atoms-family 1) (if (and (= (strlen a) (strlen a)) (wcmatch (strcase a) "C:*")) (setq out (cons a out))))
  (d8:arr (vl-sort out '<)))

;;; ---------------------------------------------------------------- main
(defun c:D8REF (/ t0 res name fn r saved out-env now manifest ss)
  (setq *d8-acad* (vlax-get-acad-object) *d8-doc* (vla-get-ActiveDocument *d8-acad*) *d8-ms* (vla-get-ModelSpace *d8-doc*))
  (if (ssget "_X") (progn (princ "\nThe drawing is not empty. Use QNEW and run D8REF again. Nothing was changed.") (exit)))
  (setq out-env (getenv "D8_REF_OUT"))
  (setq *d8-out* (vl-string-translate "\\" "/"
                   (if (and out-env (/= out-env "")) out-env
                       (getstring T "\nOutput folder (empty folder recommended): "))))
  (if (not (d8:mkdirs *d8-out*)) (progn (princ "\nCould not create the output folder.") (exit)))
  (setq saved (list (getvar "FILEDIA") (getvar "CMDECHO") (getvar "EXPERT")))
  (setvar "FILEDIA" 0) (setvar "CMDECHO" 0) (setvar "EXPERT" 5)
  (vla-StartUndoMark *d8-doc*)
  (setq res nil t0 (getvar "DATE"))
  (foreach s *d8-scenarios*
    (setq name (car s) fn (cdr s))
    (setq r (vl-catch-all-apply fn nil))
    (setq res (cons (cons name
                          (if (vl-catch-all-error-p r)
                              (d8:obj (list (cons "status" "error") (cons "error" (vl-catch-all-error-message r))))
                              (d8:obj (list (cons "status" "ok") (cons "values" (d8:obj r))))))
                    res))
    ;; clean slate for the next scenario
    (vlax-for o *d8-ms* (vl-catch-all-apply 'vla-Delete (list o)))
    (while (> (getvar "CMDACTIVE") 0) (command "")))
  (vla-EndUndoMark *d8-doc*)
  (d8:write "measurements.json" (d8:js (d8:obj (reverse res))))
  (d8:write "commands.json" (d8:js (d8:obj (list (cons "menus" (vl-catch-all-apply-val '(lambda () (d8:arr (d8:menus)))))
                                                (cons "toolbars" (vl-catch-all-apply-val '(lambda () (d8:arr (d8:toolbars)))))
                                                (cons "lisp_defined_commands" (d8:lisp-commands))
                                                (cons "system_variables" (d8:sysvars))
                                                (cons "note" "AutoCAD has no single call that lists all built-in commands; menus and toolbars are enumerated through ActiveX. The owner also exports the command alias file and the CUIx by hand (README).")))))
  (setq manifest
    (d8:obj (list (cons "harness" "dino8-reference-autocad") (cons "harness_version" *d8-version*) (cons "tested_against_real_application" nil)
                  (cons "program" "AutoCAD") (cons "acadver" (getvar "ACADVER")) (cons "product" (getvar "PRODUCT")) (cons "release" (getvar "RELEASE"))
                  (cons "platform" (getvar "PLATFORM")) (cons "locale" (getvar "LOCALE")) (cons "com_version" (vla-get-Version *d8-acad*))
                  (cons "julian_date" (getvar "DATE"))
                  (cons "settings" (d8:obj (list (cons "insunits" (getvar "INSUNITS")) (cons "measurement" (getvar "MEASUREMENT")) (cons "lunits" (getvar "LUNITS"))
                                                 (cons "luprec" (getvar "LUPREC")) (cons "isolines" (getvar "ISOLINES")) (cons "facetres" (getvar "FACETRES"))
                                                 (cons "filedia_restored_to" (car saved)))))
                  (cons "scenario_count" (length *d8-scenarios*)))))
  (d8:write "manifest.json" (d8:js manifest))
  (setvar "FILEDIA" (car saved)) (setvar "CMDECHO" (cadr saved)) (setvar "EXPERT" (caddr saved))
  (princ (strcat "\nDino 8 reference run finished. Output: " *d8-out*))
  (princ))
(princ "\nDino 8 reference harness loaded. Type D8REF in an EMPTY drawing (QNEW).")
(princ)
